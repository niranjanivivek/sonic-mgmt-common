module openconfig-system-annot {

    yang-version "1";

    namespace "http://openconfig.net/yang/openconfig-system-annot";
    prefix "oc-sys-annot";

    import openconfig-system { prefix oc-sys; }
    import openconfig-yang-types { prefix oc-yang; }
    import openconfig-system { prefix oc-sys; }
    import gnsi-credentialz { prefix gnsi-credz; }
    import gnsi-pathz { prefix gnsi-pathz; }
    import sonic-extensions {prefix sonic-ext; }
    import openconfig-system-grpc { prefix oc-sys-grpc; }

    deviation /oc-sys:system/oc-sys-grpc:grpc-servers {
        deviate add {
            sonic-ext:key-transformer "grpc_server_key_xfmr";
            sonic-ext:subtree-transformer "grpc_server_xfmr";
        }
    }

    deviation /oc-sys:system/gnsi-pathz:gnmi-pathz-policies {
      deviate add {
        sonic-ext:key-transformer "pathz_policies_key_xfmr";
        sonic-ext:subtree-transformer "pathz_policies_xfmr";
      }
    }
}
